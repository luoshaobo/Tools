CCM-CommonTypes {1 3 6 1 4 1 37916 6 0 2} DEFINITIONS AUTOMATIC TAGS ::= BEGIN

    IMPORTS
           UINT32     FROM FS-StandardTypes
    ;
	
	INT32  ::= INTEGER (-2147483648..2147483647)
	
    -- CCM Version information
    SchemaPackageVersion  ::= INT32 (1)

    -- PreliminaryVersion to be removed from official versions
    PreliminaryVersion    ::= INT32 (9)
    SignalFlowVersions    ::= SEQUENCE OF INT32 (1)

    -- 1 - In alphabetic order
    MessageId ::= OCTET STRING (SIZE(2))

    NanoSeconds ::= INTEGER(0..999999999)

    Timestamp ::= SEQUENCE {
       tvSec   UINT32,
       tvNsec  NanoSeconds OPTIONAL,
       ...
    }

    TimeToLiveSeconds   ::= INT32(1.. maxTimeToLiveSeconds)

     -- 2 years (365+366) days in seconds
    maxTimeToLiveSeconds    INT32 ::= 63158400

    TimeToLiveMilliSeconds  ::=   INT32(1.. maxTimeToLiveMilliSeconds)

    -- 1 hour in milliseconds
    maxTimeToLiveMilliSeconds     INT32 ::= 3600000


    TransactionId ::= OCTET STRING (SIZE(6)) 

    Uri ::= UTF8String

    UUID ::= OCTET STRING (SIZE(16)) 

    -- 2 - Standard integer types (see also FS-StandardTypes)
    UINT1  ::= INTEGER (0..1)    
    UINT2  ::= INTEGER (0..3)    
    UINT4  ::= INTEGER (0..15)    
    
END
