-- Module Document-Set-Descriptor (T.424:07/1996)
Document-Set-Descriptor {2 8 1 14 1} DEFINITIONS ::=
BEGIN

EXPORTS Document-Set;

IMPORTS
  Interchange-Data-Element
    FROM Interchange-Data-Elements {2 8 1 5 5}
  --  see ITU-T Rec. T.415 | ISO/IEC 8613-5
  Document-Set-Profile-Descriptor
    FROM Document-Set-Profile-Descriptor
      
  --  see 8.11.2
  Link-Class-Descriptor, Link-Descriptor, Enciphered-Link-Descriptor
    FROM Link-Descriptors;

--  see 8.11.3
Document-Set ::= SEQUENCE {
  profile           Document-Set-Profile-Descriptor,
  link-classes      [0]  SET OF Link-Class-Descriptor OPTIONAL,
  links             [1]  SET OF Link-Descriptor OPTIONAL,
  nodes             [2]  SET OF Interchange-Data-Element OPTIONAL,
  enciphered-links  [3]  SET OF Enciphered-Link-Descriptor OPTIONAL
}

END

-- Generated by Asnp, the ASN.1 pretty-printer of France Telecom R&D
