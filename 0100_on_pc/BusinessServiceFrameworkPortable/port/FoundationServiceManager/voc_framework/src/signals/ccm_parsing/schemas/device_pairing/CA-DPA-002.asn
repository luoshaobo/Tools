CA-DPA-002 {1 3 6 1 4 1 37916 3 8 7 0 0 2} DEFINITIONS AUTOMATIC TAGS ::= BEGIN

    IMPORTS 
        ResponseInfo                        FROM FS-StandardTypes
        DevicePairingId, SessionId          FROM CA-CommonTypes
        ;

    CA-DPA-002 ::= SEQUENCE {
        id                               DevicePairingId,
        responseInfo                     ResponseInfo,
        status          CHOICE {
           initiated    NULL,
           finished     FinishedStatus,
           ...
        } OPTIONAL,
        remoteConnectionSessionId    SessionId OPTIONAL,
        ...
    }

    FinishedStatus ::= ENUMERATED {
        stoppedByCommand                    (0),
        terminatedRemoteConnectionTimeout   (1),
        terminatedPairingTimeout            (2),
        ...
    }    

END
