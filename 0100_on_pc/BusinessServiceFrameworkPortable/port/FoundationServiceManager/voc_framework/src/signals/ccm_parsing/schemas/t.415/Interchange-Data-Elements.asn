-- Module Interchange-Data-Elements (T.415:03/1993)
Interchange-Data-Elements {2 8 1 5 5} DEFINITIONS ::=
BEGIN

EXPORTS Interchange-Data-Element;

IMPORTS
  Document-Profile-Descriptor
    FROM Document-Profile-Descriptor --  see 7.7 
      
  Layout-Class-Descriptor, Layout-Object-Descriptor
    FROM Layout-Descriptors --  see 7.9 
      
  Logical-Class-Descriptor, Logical-Object-Descriptor
    FROM Logical-Descriptors --  see 7.10
      
  Presentation-Style-Descriptor, Layout-Style-Descriptor
    FROM Style-Descriptors --  see 7.11
      
  Text-Unit
    FROM Text-Units --  see 7.13
      
  Sealed-Doc-Prof-Descriptor, Enciphered-Doc-Prof-Descriptor,
    Preenciphered-Bodypart-Descriptor, Postenciphered-Bodypart-Descriptor
    FROM Protected-Part-Descriptors --  see 7.15
      
  Link-Class-Descriptor, Link-Descriptor, Enciphered-Link-Descriptor
    FROM Link-Descriptors {2 8 1 14 3};

--  See ITU-T Rec. T.424 | ISO/IEC 8613-14
Interchange-Data-Element ::= CHOICE {
  document-profile                    [0] IMPLICIT Document-Profile-Descriptor,
  layout-object-class                 [1] IMPLICIT Layout-Class-Descriptor,
  layout-object                       [2] IMPLICIT Layout-Object-Descriptor,
  content-portion                     [3] IMPLICIT Text-Unit,
  logical-object-class                [5] IMPLICIT Logical-Class-Descriptor,
  logical-object                      [6] IMPLICIT Logical-Object-Descriptor,
  presentation-style
    [7] IMPLICIT Presentation-Style-Descriptor,
  layout-style                        [8] IMPLICIT Layout-Style-Descriptor,
  sealed-doc-prof-descriptor          [9] IMPLICIT Sealed-Doc-Prof-Descriptor,
  enciphered-doc-prof-descriptor
    [10] IMPLICIT Enciphered-Doc-Prof-Descriptor,
  preenciphered-bodypart-descriptor
    [11] IMPLICIT Preenciphered-Bodypart-Descriptor,
  postenciphered-bodypart-descriptor
    [12] IMPLICIT Postenciphered-Bodypart-Descriptor,
  link-class                          [13] IMPLICIT Link-Class-Descriptor,
  link                                [14] IMPLICIT Link-Descriptor,
  enciphered-link-descriptor          [15] IMPLICIT Enciphered-Link-Descriptor
}

END

-- Generated by Asnp, the ASN.1 pretty-printer of France Telecom R&D
