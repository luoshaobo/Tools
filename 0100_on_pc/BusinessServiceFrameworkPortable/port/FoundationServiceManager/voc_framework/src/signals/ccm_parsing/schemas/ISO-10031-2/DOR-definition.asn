-- Module DOR-definition (ISO/IEC 10031-2:1991)
 -- See also ITU-T formal description search tool
 -- See also the index of all ASN.1 assignments needed in this Recommendation

--
-- Copyright © ISO/IEC 1991. This version of
-- this ASN.1 module is part of ISO/IEC 10031-2:1991;
-- see the ISO|IEC text itself for full legal notices.
-- 
DOR-definition {joint-iso-itu-t dor(4) reference-definition(0)} DEFINITIONS ::=
BEGIN

EXPORTS
  AE-Identifier, Altered-value, DOR, dor-abstract-syntax, dor-syntax-asn1,
    dorx, Extend-QoS, Local-reference, Locational-identifier, Produce-QoS,
    QoS-level, Quality-of-Service, Requested-QoS-level,
    Single-use-of-reference, Token;

IMPORTS
  DistinguishedName
    FROM InformationFramework {joint-iso-itu-t ds(5) module(1)
      informationFramework(1) 3}
  PresentationAddress
    FROM SelectedAttributeTypes {joint-iso-itu-t ds(5) module(1)
      selectedAttributeTypes(5) 3};

-- Defined Object Identifiers
dorx OBJECT IDENTIFIER ::=
  {joint-iso-itu-t dor(11)}

-- Object identifier for abstract syntax of DOR
dor-abstract-syntax OBJECT IDENTIFIER ::=
  {dorx reference-abstract-syntax(1)}

-- Object identifier for abstract syntax of DOR with basic ASN.1 encodings in
-- EXTERNAL
dor-syntax-asn1 OBJECT IDENTIFIER ::=
  {dorx reference-syntax(2) asn1(0)}

-- Definition of DOR type
DOR ::= SEQUENCE {
  ae-identifier       [0]  AE-Identifier OPTIONAL,
  --  mandatory in case of produce-operations and consume-operations
  local-reference     [1]  Local-reference,
  data-object-type    OBJECT IDENTIFIER,
  -- identifying the abstract syntax and  the transfer syntax of the
  -- referenced data value
  quality-of-service  [2]  Quality-of-Service DEFAULT {},
  token               [3]  Token OPTIONAL
}

AE-Identifier ::= SEQUENCE { -- at least one component shall be present
  locational-identifier        [0]  Locational-identifier OPTIONAL,
  direct-logical-identifier    [1]  DistinguishedName OPTIONAL,
  indirect-logical-identifier  [2]  DistinguishedName OPTIONAL
}

Locational-identifier ::= SEQUENCE {
  presentation-address  [0]  PresentationAddress,
  ae-title              [1]  AE-title OPTIONAL,
  -- as defined in ISO 8650:1988/Cor.1:1990 
  application-contexts  SET OF OBJECT IDENTIFIER
}

Local-reference ::= SEQUENCE {
  application         [0]  OCTET STRING OPTIONAL,
  specific-reference  [1]  OCTET STRING
}

Quality-of-Service ::= SEQUENCE {
  qoS-level           [0]  QoS-level DEFAULT level-1:NULL,
  usage-of-reference  Single-use-of-reference DEFAULT TRUE
}

QoS-level ::= CHOICE {
  level-1  [1] IMPLICIT NULL,
  level-2  [2] IMPLICIT GeneralizedTime,
  -- specifying the produce time 
  level-3
    [3] IMPLICIT SEQUENCE {produce-time   GeneralizedTime,
                           fidelity-time  GeneralizedTime}
}

Single-use-of-reference ::= BOOLEAN

Token ::= CHOICE {
  simpletoken    OCTET STRING,
  -- used to validate an access which use this DOR
  externaltoken  EXTERNAL -- for future proxy mechanism
}

-- Data types for produce-operations
Produce-QoS ::= SEQUENCE {
  qoS-level           [0]  Requested-QoS-level DEFAULT level-1:NULL,
  usage-of-reference  Single-use-of-reference DEFAULT TRUE
}

Requested-QoS-level ::= CHOICE {
  level-1  [1] IMPLICIT NULL,
  level-2  [2] IMPLICIT NULL,
  level-3  [3] IMPLICIT GeneralizedTime
  -- specifying the requested fidelity-time
}

-- Data types for extending a specific QoS
Extend-QoS ::= SEQUENCE {
  qoS-level           [0]  Requested-QoS-level OPTIONAL,
  -- if omitted, no change required
  usage-of-reference  Single-use-of-reference OPTIONAL
  -- if omitted, no change required
}

-- Data types for requesting / indicating value alteration in produce-operation
-- or access-operation
Altered-value ::= ENUMERATED {
  value-not-altered(1), value-altered(2), undefined(3)}

-- dw: definition of AE-title, as defined in ISO 8650:1988/Cor.1:1990 
-- dw: defined in-line here so we don't need to import it, original comments
-- dw: are as they appear in the 8650:1988 Annex E
AP-title ::= TYPE-IDENTIFIER.&Type

-- The exact definition and values used for AP-title
-- should be chosen taking into account the ongoing 
-- work in areas of naming, the Directory, and the 
-- Registration Authority procedures for AE titles,
-- AE titles, and AE qualifiers
AE-qualifier ::= TYPE-IDENTIFIER.&Type

-- The exact definition and values used for AE-qualifier
-- should be chosen taking into account the ongoing 
-- work in areas of naming, the Directory, and the 
-- Registration Authority procedures for AE titles,
-- AE titles, and AE qualifiers
AE-title ::= SEQUENCE {ap  AP-title,
                       ae  AE-qualifier
}

END -- of DOR-definition

-- Generated by Asnp, the ASN.1 pretty-printer of France Telecom R&D
