-- Vehicle Data Service Protocol
-- Ecarx Connected Vehicle Cloud
--
-- VDS FOTA
-- 
-- Current Version:  1.3.12

--Version 1.3.12 draft, 2018-12-12

-- 20181212
-- GEEA2.0 OTA
-- All signal lengths are based on In-car IP signal lengths.
-- serviceParameters and ServiceParam is generic service parameters used for extension,There is no special specification and no need to interpret this information
-- changes log
-- ADD 2018.12.20 
-- fota and RVDC share LanguageSetting VDS 
-- fota vds file and RVDC VDS file merge to geea2.0 OTA vds file
-- ClientHmiVehicleSettings and RvdcForcedSetting All settings must pass values, and the original values should be brought in without modification.
--  fota and RVDC root node add vin 
-- fota and RVDC root node add appId is that  Which platform to use OTA Server
-- END 2018.12.20
-- ADD 2018.12.25 
-- In InstallationInstruction the ecuRemaining VDS from InstallationInstruction   node  move to  Instruction for support one time push many ECU Instructions
-- delete CharEncoding VDS
-- AvailableAssignment the element of critical to workshop-installation.
-- AvailableAssignment the occurs of the element long-description from 1to 0..1
-- assignmentNotification Add the element deltatime used for scheduled update  This parameter used for scheduled update.unit s
-- InstallationInstruction  the requiredpreparationtime unit from seconds to milliseconds.
-- InstallationInstruction  the expectedinstallationtime unit from seconds to milliseconds.
-- InstallationInstruction  the estimatedinstallationtime unit from seconds to milliseconds.
-- InstallationInstruction  the occurs of the element validationtype from 0..1 to 1
-- InstallationSummary   the totalInstallationTime unit from seconds to milliseconds.
-- InstallationSummary   the measuredInstallationTime unit from seconds to milliseconds.
-- MeasurementAssignment  Delete the trigger type of push

-- END 2018.12.25 
-- ADD 2018.12.26 
-- softwarePartStatus clientVersion ecuAddress  validationKey  Unification is PrintableString(SIZE(1..256))
-- trigger type from Boolean to ENUMERATED.
-- operator type from Boolean to ENUMERATED.
-- timestamp type becomes to 	PrintableString(SIZE(1..32))
-- delete the ExceptionReport of clientVersion
-- in ExceptionReport except timestamp?? issuerid  and exceptionmessage is Mandatory, other is OPTIONAL
-- in ExceptionMessage exception type becomes to PrintableString
-- installationOrderId type becomes to UTF8String
-- MeasurementAssignment  add the trigger type of push?
-- end 2018.12.26 

VDS-FOTA DEFINITIONS AUTOMATIC TAGS ::= BEGIN

-- RVDC START
 RVDC ::= SEQUENCE {
	appId			AppId ,-- Which platform to use OTA Server
	maOrderId		PrintableString(SIZE(1..512)),-- The orderId is generated by the command initiator, and the responder needs to response it to the initiator.	
	timestamp              	PrintableString(SIZE(1..32)),-- The client recorded time of the notification
	-- The VIN is used to make sure a MA is not sent to cars which are not supposed to have the MA. This is also used for Signature verification
	vin			PrintableString(SIZE(1..128)),-- Vehicle identification code 
	maBusinessType 		MaBusinessType,-- the business type of the current operation
	rvdcSetting		RvdcSetting OPTIONAL, 
	assignmentNotification	RvdcAssignmentNotification OPTIONAL,
	maSynchronizationReq 	MaSynchronizationReq OPTIONAL,
	maSynchronization 	MaSynchronization OPTIONAL, -- Support vehicle request to cloud for response and cloud to vehicle for push
	exceptionHandling	RvdcExceptionHandling OPTIONAL,
	measurementDataPackage	MeasurementDataPackage OPTIONAL
}

-- the business type of the current operation
MaBusinessType ::= ENUMERATED {
	rvdcSetting    		(0), --  set RVDC Authorization Status
	assignmentNotification	(1), --   Synchronization status between Server and end. 
	maSynchronizationReq	(2),--  end to request MAs from RVDC server
	maSynchronization	(3),  -- Support vehicle request to cloud for response and cloud to vehicle for push
	exceptionHandling	(4),
	measurementDataPackage	(5)
}

RvdcSetting ::= SEQUENCE {
	maSetting	MaSetting OPTIONAL,-- The objective of this interface is to set RVDC Authorization Status for cloud to end or end to cloud
	vehicleSetting	RvdcVehicleSetting OPTIONAL,-- The objective of this interface is to provide RVDC vehicle settings to vehicle.
	languageSetting LanguageSetting OPTIONAL, -- The objective of this interface is to provide the changed language setting of in-vehicle HMI to RVDC server.
	forcedSetting RvdcForcedSetting OPTIONAL,
	serviceParameters		SEQUENCE OF ServiceParameter OPTIONAL 	-- generic service parameters used for extension
}

-- The objective of this interface is to provide a forced setting to vehicle to suppress, lock and make the RVDC setting invisible in the HMI.
RvdcForcedSetting ::= SEQUENCE {
	visibility	BOOLEAN ,-- Shall be set to true when make the RVDC setting invisible in the HMI. 0 is Invisible, 1 is Visible
	suppress	BOOLEAN ,-- Shall be set to true when make the RVDC setting suppress in the HMI. 0 is not suppress, 1 is suppress
	lock		BOOLEAN   -- Shall be set to true when make the RVDC setting lock in the HMI. 0 is unlock, 1 is lock
}

RvdcVehicleSetting ::= SEQUENCE {
	-- ON - the client (vehicle) is active for RVDC function, i.e. the vehicle will synchronize with the backend,measurement assignments will identified for download.
	-- OFF - the client is inactive i.e. the vehicle will no longer synchronize with the backend, measurement assignments will no longer be identified for download.
	-- The setting shall be disabled (OFF) until the end-user has agreed to the terms of service agreement (RVDC Customer setting).
	rvdcFunction		BOOLEAN,
	--  Numeric value defining the number of milliseconds to delay start of MA execution after going to UM = Driving.
	-- The default value is 60s.
	-- UNIT:s
	collectOffSetTime	INTEGER(1..512) 
}

--The objective of this interface is to set RVDC Authorization Status for cloud to end or end to cloud
MaSetting ::= SEQUENCE {
	collectFunction		BOOLEAN,-- True if the RVDC function is activated and if set to false ,no matter what dataCollection and remoteDiagnostics to set,
	authorizationStatus	AuthorizationStatus
}

-- Authorization Status
AuthorizationStatus ::= SEQUENCE {
	dataCollection		BOOLEAN OPTIONAL,-- True if data collection is enabled
	remoteDiagnostics	BOOLEAN OPTIONAL --  True if full remote diagnostics is enabled for the vehicle
}

--The objective of this interface is to provide Synchronization status between Server and end
-- eg 	
--	1.When MA has installed or executed completed in vehicle 
--  2.Exception occurs when synchronizing, downloading, installing the MA
--	3.The objective of this interface is to provide the RVDC Authorization Status setting result to RVDC server.
--	4.The objective of this interface is to provide current assignment notification to vehicle.
RvdcAssignmentNotification ::= SEQUENCE {
	maCarId		INTEGER(1..4294967295) OPTIONAL,				-- Identifier derived from associated MA
	maVersion	INTEGER(1..4294967295) OPTIONAL, 				-- Version derived from associated MA
	newStatus	PrintableString(SIZE(1..128)),		-- Notification of transition to new status or state by the client (vehicle)
	timestamp	PrintableString(SIZE(1..32)),-- The client recorded time of the notification
	reason		PrintableString(SIZE(1..512)) OPTIONAL 	-- Reason for the transition
}

-- The objective of this interface is to request MAs from RVDC server
-- The message will be triggered from vehicle:
--	When automatic synchronization of assignments has been set by end-user the Vehicle
--	Diagnostic Data Collection shall trigger a MA synchronization as soon as possible after the latest request to the server has expired.
MaSynchronizationReq ::= SEQUENCE {
	-- The current size of MA storage quota in kilobytes [kB] in vehicle resolution is 100kb/bit
   storageQuota 		INTEGER(1..4294967295) ,
	-- Version derived from associated MA
   maFormatVersion 		INTEGER(1..4294967295),-- The cloud sends corresponding data according to the version reported by the vehicle. If the version of the vehicle changes, the cloud needs to be notified first.
   installedMa	SEQUENCE OF Ma OPTIONAL, -- installed measurements in vehicle
	-- There is no special specification and no need to interpret this information
   serviceParameters		SEQUENCE OF ServiceParameter OPTIONAL	-- generic service parameters used for extension,
   
}

-- The objective of this interface is to provide MAs to vehicle.
MaSynchronization ::= SEQUENCE {
	removeMas 	SEQUENCE OF Ma OPTIONAL ,-- These MAs shall be removed
	newMas		SEQUENCE OF MeasurementAssignment OPTIONAL , -- New or updated MAs
	serviceParameters		SEQUENCE OF ServiceParameter OPTIONAL	-- generic service parameters used for extension
}

Ma ::= SEQUENCE {
	maId			INTEGER(1..4294967295),
	maVersion 		INTEGER(1..4294967295)	
}

-- ForcedMA 	
MeasurementAssignment ::= SEQUENCE {
	maId			INTEGER(1..4294967295),
	maVersion 		INTEGER(1..4294967295),
	vin			PrintableString(SIZE(1..128)),-- The VIN is used to make sure a MA is not sent to cars which are not supposed to have the MA. This is also used for Signature verification.
	maFormatVersion		INTEGER(1..4294967295), -- Describes the protocol version of the MA. This must be the same as the SW in vehicle gateway
	maExecutionPriority 	INTEGER(1..65535), -- The execution priority of the MA
	telematicsParameters	TelematicsParameters,-- This contains telematics parameters
	usageModesAllowed	INTEGER(1..4294967295),-- Shall equal the usage mode signal, only values active or driving are allowed.
	startCondition		PrintableString(SIZE(1..32)),-- The start time for the MA
	stopCondition		StopCondition,-- The condition to stop the MA. At least one stop condition must be chosen. This shall be checked during parsing.
	retentiondate		PrintableString(SIZE(1..32)),-- The retention date for the MA.
	authorizationStatus	AuthorizationStatus,-- The authorization status needed to perform the MA		
	executionTrigger	ExecutionTrigger,-- The type of execution trigger in the MA. Only one trigger type can be chosen.
	ecusAndPartNumbers	SEQUENCE OF EcusAndPartNumber, -- The number of ECUs which are needed to perform MA.
	diagnosticCommand	SEQUENCE OF DiagnosticCommand ,-- Specifies the diagnostic commands to be executed
	dataIntegrityCheck	PrintableString(SIZE(1..64)), -- This shall be a CRC32 over the entire payload.
	serviceParameters		SEQUENCE OF ServiceParameter OPTIONAL	-- generic service parameters used for extension
	
}

EcusAndPartNumber ::= SEQUENCE {
	ecuAddress	PrintableString(SIZE(1..256)),-- This shall contain the ECU ID for the first ECU
	diagnosticPartNumber PrintableString(SIZE(1..64)) -- This contains the diagnostic part number
}

ExecutionTrigger ::= SEQUENCE {
	-- Push MA is executed as soon as possible hence it does not have any specific trigger.
	push		BOOLEAN,
	uds		UDS OPTIONAL,-- Trigger is based on collection of UDS data and comparison, see requirement
	time		Trigger OPTIONAL,-- Trigger is based on time interval
	drivingCycle 	Trigger OPTIONAL --Trigger is based on driving cycle interval
}

Trigger ::= SEQUENCE {
	trigger		TriggerType ,-- This contains if the collection of data shall be carried out on start or end of a DCY. startofdcy (0),endofdcy (1)
	-- if Trigger is time ,interval is time interval. if Trigger is drivingCycle ,interval is driving cycle interval
	interval	INTEGER(1..4294967295)  
}

-- This contains if the collection of data shall be carried out on start or end of a DCY. startofdcy (0),endofdcy (1)
TriggerType ::= ENUMERATED {
    startofdcy (0),
    endofdcy (1)
}

UDS ::= SEQUENCE {
	operator			Operator, -- The operator between the diagnostic trigger commands. 0 = Or 1 = And
	delayForNextTriggerCheck 	INTEGER(1..4294967295), -- This contains the time between two trigger checks, it is specified in seconds.
	-- This is specifying an additional time delay until the next trigger check, after data has been collected. This can be used to not collected multiple MDPs with same content. The delay is specified in seconds. This delay can be 0.
	delayAfterCollection		INTEGER(1..4294967295), 
	diagnosticCommands	SEQUENCE OF DiagnosticCommand -- This contains the actual trigger commands
}

--The operator between the diagnostic trigger commands
Operator ::= ENUMERATED {
    or (0),
    and (1)
}

-- if using in uds,compareType and compareValue are Mandatory ,Others are OPTIONAL
DiagnosticCommand ::= SEQUENCE {
	ecuAddress			PrintableString(SIZE(1..256)), -- This is the ECU target address for the request. 
	serviceId			PrintableString(SIZE(1..64)), -- This is the UDS service to be used
	input				PrintableString(SIZE(1..65535)), -- This is the input to be added after the UDS service, this can contain sub service ID,Identifiers and/or other input data to the ECU.
	compareType			CompareType OPTIONAL,
	compareValue			PrintableString(SIZE(1..65535)) OPTIONAL, -- This is the value to compare the ECU response to.
	delayUntilNextTriggerCommand 	INTEGER(1..512) -- This is the time to wait between two diagnostic trigger commands, this is specified din seconds.
}

CompareType ::= ENUMERATED {
	equalto 		(1),
	greaterthan 		(2),
	greaterthanorequal 	(3),
	lessthan 		(4),
	lessthanorequal 	(5)
}

-- This contains telematics parameters
TelematicsParameters ::= SEQUENCE {
	timeToLive	INTEGER(1..4294967295), -- This ELEMENT describes how many seconds the maximum transmission time is before the MDP is discarded.
	uploadPriority	INTEGER(1..255)  -- This contains the type of upload channels the telematics unit can use.
}

-- The condition to stop the MA. At least one stop condition must be chosen. This shall be checked during parsing.
StopCondition ::= SEQUENCE {
	period	INTEGER(1..65535) OPTIONAL,-- The amount of days the MA shall be performed after the first successfully collected MDP.
	amount	INTEGER(1..65535) OPTIONAL,-- The amount of successful collections to be made.
	time	PrintableString(SIZE(1..32)) OPTIONAL-- The stop time for the MA. The timestamp is defined in the requirement
}

-- The objective of this interface is to provide Measurement Data Package to RVDC server.
-- The message will be triggered from vehicle:  When the MDP upload conditions are met.
MeasurementDataPackage ::= SEQUENCE {
	telematicsParameters	TelematicsParameters,-- the onboard telematics unit parameters
	serviceParameters		SEQUENCE OF ServiceParameter OPTIONAL,	-- generic service parameters used for extension
	mdp			Mdp	-- actual data payload

}

Mdp ::= SEQUENCE {
	mdpFormatVersion	INTEGER(1..256),-- This is version of the MDP format which the ECU sends the data.
	vin			PrintableString(SIZE(1..128)),	-- The VIN of the vehicle, used to make sure signature is car unique.
	ma			Ma,
	sequenceNumber		INTEGER(1..4294967295),-- Shall contain the MA Sequence counter value.
	timestampReadOutStart	PrintableString(SIZE(1..32)),-- The timestamp of the first diagnostic response was collected
	udsTriggerId		PrintableString(SIZE(1..64)) OPTIONAL, -- If the execution trigger was "UDS", this ELEMENT contains the ID of the condition which triggered the readout if the condition operator was set to "OR".
	diagnosticResponse	PrintableString(SIZE(1..65535)) --The raw response of the diagnostic request. The string must have dynamic length.
}

-- The objective of this interface is to provide HMI Exception Handling to RVDC server.
RvdcExceptionHandling ::= SEQUENCE {
	exceptionName	UTF8String(SIZE(1..128)),
	description	UTF8String(SIZE(1..512)),
	publisher 	UTF8String(SIZE(1..128)),
	severity	UTF8String(SIZE(1..128)) OPTIONAL,
	impact		UTF8String(SIZE(1..128)) OPTIONAL,
	action		UTF8String(SIZE(1..128)) OPTIONAL
}
-- RVDC END

-- FOTA START
 FOTA ::= SEQUENCE {
	appId				AppId ,-- Which platform to use OTA Server
	-- The VIN is used to make sure a MA is not sent to cars which are not supposed to have the MA. This is also used for Signature verification
	vin			PrintableString(SIZE(1..128)),-- Vehicle identification code 
	dataType 			DataType,
	clientConfSyncRequest		ClientConfSyncRequest OPTIONAL, -- provide Client Configuration to OTA server.
	inventoryInstruction		InventoryInstruction OPTIONAL,-- The objective of this interface is to provide Inventory Instruction to vehicle
	availableAssignmentRequest	AvailableAssignmentRequest OPTIONAL,-- The objective of this interface is to request available assignment from OTA server.
	availableAssignment		AvailableAssignment  OPTIONAL,-- The objective of this interface is to provide available assignment to vehicle.
	installationInstruction		InstallationInstruction OPTIONAL,-- The objective of this interface is to provide Installation Instructions to vehicle
	installationSummary		InstallationSummary OPTIONAL, -- The objective of this interface is to provide Installation Summary to OTA server.
	ecuExceptionReport		EcuExceptionReport OPTIONAL ,  -- The objective of this interface is to provide Exception Reports to OTA server
	clientHmiVehicleSettings	ClientHmiVehicleSettings OPTIONAL,-- Due to fleet management and administrative reasons, the backend may lock certain vehicle settings in order to force a setting value for specific vehicles
	assignmentData			AssignmentData OPTIONAL,-- The objective of this interface is to provide assignment data to vehicle	
	assignmentNotification		FotaAssignmentNotification OPTIONAL,
	otaAssignmentFileInfo		OtaAssignmentFileInfo OPTIONAL
}

DataType ::= ENUMERATED{
	clientConfSyncRequest    	(0),
	ecuExceptionReport  		(1),
	inventoryInstruction 	        (2),
	availableAssignmentRequest	(3),
	availableAssignment		(4),
	installationInstruction		(5),
	assignmentNotification		(6),
	clientHmiVehicleSettings	(7),
	assignmentData			(8),
	otaAssignmentFileInfo		(9),
	installationSummary		(10)
}

-- The objective of this interface is to detect if match for the currently stored Client Configuration
-- (client_version) in vehicle and the currently stored Expected Client Configuration (server_version) in OTA server
-- apply to  geea2.0 ota 2.1.3,2.4.3
ClientConfSyncRequest ::= SEQUENCE {
	-- The client recorded time of the notification
	timestamp              	PrintableString(SIZE(1..32)),
	-- Client Version defining the Client Configuration version.
	clientVersion		PrintableString(SIZE(1..256)),
	-- ECU Inventory detailing the validated content of each a target ECU.
	ecuInventory		SEQUENCE OF EcuInventory OPTIONAL
}

-- Provide Inventory Instruction to vehicle. 
-- apply to  geea2.0 ota 2.3.3
InventoryInstruction ::= SEQUENCE {
	--The parsing structure used to mark inventory instruction
	inventoryInstructionVersion  PrintableString(SIZE(1..32)),
	-- ECU inventory information
	ecuInstructions  SEQUENCE OF EcuInventory
}

-- ECU inventory information
EcuInventory ::= SEQUENCE {
	-- ECU Address
	ecuAddress	 	PrintableString(SIZE(1..256)),
	
	-- Validation Key (DID) used by the client to obtain ECU Part Identifiers using UDS
	validationKeys 		SEQUENCE OF ValidationKey,
		
	-- Detailed Exception Message, detailing an exception
	-- Detailed Exception Message, detailing an exception.
	-- No response or final response received from the server (ECU) within timeout.
	-- no-response (0),
	-- The ECU response could not be interpreted by the client due to invalid length or data.
	-- invalid-data (1),
	-- ECU responds with negative response code (NRC) other than pending response. I.e. the ECU rejects the request.
	-- nrc (2),
	-- Maximum number of allowed repeat request times reached.
	-- repeat-request-max-reached (3)
	exceptionMessage  	UTF8String(SIZE(1..65535)) OPTIONAL
}

ValidationKey ::= SEQUENCE {
	-- Validation Key (DID) used by the client to obtain ECU Part Identifiers using UDS
	validationKey 		PrintableString(SIZE(1..256)),	
	-- Part Identifier returned by the target ECU when requesting ECU key  
	partIdentifiers  	SEQUENCE OF PrintableString(SIZE(1..256)) OPTIONAL
}

-- apply to  geea2.0 ota 2.6.3
AvailableAssignmentRequest ::= SEQUENCE {
	languageSetting LanguageSetting
}

-- apply to  geea2.0 ota 2.7.3
AvailableAssignment ::= SEQUENCE {
	--Unique Identifier for the commissioned assignment. 
	installationOrderId  UTF8String(SIZE(1..256)),	
	timestamp          PrintableString(SIZE(1..32)),	
	--Shall be set to 'true' if the assignment is intended for workshop preparation i.e. the assignment is only allowed to be installed in a workshop
	workshopInstallation	   BOOLEAN,	
	--The total download size in kilobytes [kB] for the assignment. 
	downloadsize       INTEGER(1..2147483647),	
	--The total installation time in seconds [s] for the assignment during which the vehicle will be unavailable
	totalinstallationTime  INTEGER(1..36000000),	
	--Notification of transition to new status or state
	newstatus	   PrintableString(SIZE(1..64)),	
	--Reason for the transition
	reason             UTF8String(SIZE(1..256)) OPTIONAL,	
	--A descriptive title of the assignment. 
	name		UTF8String(SIZE(1..256)),	
	shortDescription  UTF8String(SIZE(1..1024)) ,	
	--A combination of textblock, listelement and linefeed
	longDescription   UTF8String(SIZE(1..65535))  OPTIONAL
}

-- The objective of this interface is to provide Installation Instructions to vehicle.
-- apply to  geea2.0 ota 2.10.3
InstallationInstruction ::=SEQUENCE {
	--Unique Identifier of the Installation Order, or software, associated to the notification.
	installationOrderId  UTF8String(SIZE(1..256)),
	instructions SEQUENCE OF Instruction
}

--Installation Instructions are used to guide the correct installation of vehicle
Instruction ::=SEQUENCE{
	--Shall be decreased for each transmission of an Installation order ID, then final ECU shall have the value 0. 
	ecuRemaining       INTEGER(1..255),	
	--installation Instructions Version
	installationInstructionSversion PrintableString(SIZE(1..256)),	
	--Required Preparation Time for the vehicle to perform installation. specified in milliseconds.
	requiredPreparationTime		INTEGER(1..4294967295), 	
	--Expected Installation Time for the complete assignment.specified in milliseconds
	expectedInstallationTime	INTEGER(1..4294967295),	
	--Encrypted VIN unique security access code for CEM009
	area1112SecurityCode		PrintableString(SIZE(1..32)),	
	--Target ECU Installation Instructions detailing the instructions for each target ECU
	ecuInstructions			SEQUENCE OF EcuInstruction,
	--Assignment Validation element
	assignmentValidations		SEQUENCE OF AssignmentValidation
}

--Target ECU Installation Instructions detailing the instructions for each target ECU
EcuInstruction ::=SEQUENCE{
	--ECU Address
	ecuAddress				PrintableString(SIZE(1..256)),	
	--Number of Queued Request supported in by the target ECU
	queuedRequest				INTEGER(1..65535),	
	--The Security Access Code shall be used by the on-board Installation Master BOOT during the installation attempt during program mode (BOOT)
	securityKey				PrintableString(SIZE(1..256)),	
	--Software Part Installation Instructions, detailing instructions and data
	softwarePartInstallationInstructions	SEQUENCE OF SoftwarePartInstallationInstruction
}

--Software Part Installation Instructions, detailing instructions and data
SoftwarePartInstallationInstruction ::=SEQUENCE{
	--Part Identifier, unique identifier of the software part
	partidentifier			PrintableString(SIZE(1..256)),
	-- Estimated Installation Time,required by the data file, specified in milliseconds.
	estimatedInstallationtime	INTEGER((1..4294967295))
}

--Assignment Validation element
AssignmentValidation ::=SEQUENCE{
	--Validation Type
	validationType			PrintableString(SIZE(1..256)),	
	--ECU Address
	ecuAddress			PrintableString(SIZE(1..256)),	
	--Validation Key, used to obtain part identifiers from the target ECU
	validationkey			PrintableString(SIZE(1..256)),	
	--Part Identifier, unique identifier for expected part
	partidentifiers			SET OF PrintableString(SIZE(1..256))
}

-- apply to  geea2.0 ota 2.2.3,2.5.3,2.8.3,2.9.3,2.17.3,2.19.3
FotaAssignmentNotification ::= SEQUENCE {	
	-- Unique Identifier of the Installation Order, or software,associated to the notification.
	installationOrderId 	UTF8String(SIZE(1..256)) OPTIONAL,
	-- The client recorded time of the notification
	timestamp              	PrintableString(SIZE(1..32)),
	-- Notification of transition to new status or state by the client (vehicle)
	newStatus		PrintableString(SIZE(1..256)),
	-- Reason for the transition
	reason 			UTF8String(SIZE(1..256)) OPTIONAL,
        -- This parameter used for scheduled update. unit s or null
	deltaTime		INTEGER(1..604800) OPTIONAL,
	-- Extended Parameters. 
	serviceParams		SEQUENCE OF ServiceParameter OPTIONAL
} 

-- apply to  geea2.0 ota 2.11.3
InstallationSummary  ::= SEQUENCE {	
	--Installation Order ID
	installationOrderId		UTF8String(SIZE(1..256)),
	timestamp			PrintableString(SIZE(1..32)),
	--Total number of resets consumed due to retries
	repeatresets			INTEGER(1..255),
	-- Total Installation Time for the assignment. defined in milliseconds (ms)
	totalInstallationTime		INTEGER(1..4294967295),
	ecuSummarys			SEQUENCE OF EcuSummary
}

-- ECU Installation Summary.
EcuSummary ::= SEQUENCE {
	 -- ECU Address
	ecuAddress	 	PrintableString(SIZE(1..256)),
	--Total number of ECU Retries
	ecuRetries  		INTEGER(1..100) ,	
	-- ECU Installation Status.
	ecuStatus 		PrintableString(SIZE(1..256)), 
	 -- Software Part Installation Summary. 
	softwarePartSummarys   	SEQUENCE OF SoftwarePartSummary 
}

-- Software Part Installation Summary.
SoftwarePartSummary ::= SEQUENCE {
	-- Part Identifier identifying the Software Part
	partIdentifier  		PrintableString(SIZE(1..256)), 
	-- software Part Retries.
	partRetries   			INTEGER(1..65535) , 
	--  Measured Installation Time defined in milliseconds (ms)
	measuredInstallationTime 	INTEGER(1..36000000) , 
	-- Software Part Installation Status
	softwarePartStatus   		PrintableString(SIZE(1..256)) 
}

-- The objective of this interface is to provide Exception Reports to OTA server.
-- apply to  geea2.0 ota 2.12.3
EcuExceptionReport ::= SEQUENCE {
	--Shall be used for OTA server to know how many exception reports will come for the UUID 
	exceptionReportMsgRemaining	INTEGER(1..65535),
	exceptionReports		SEQUENCE OF ExceptionReport   -- Shall be maximum 3 reports
}

ExceptionReport  ::= SEQUENCE {	
	-- Installation Order ID, optional if Client Version is used.
	installationOrderId 	UTF8String(SIZE(1..256)) OPTIONAL,	
	timestamp              	PrintableString(SIZE(1..32)),
	--Issuer Identifier, identifying the issuer of the Exception report
	issuerId   		PrintableString(SIZE(1..256)),
	--Client Version, optional if Installation Oder ID is used
	clientConfigurationId  PrintableString(SIZE(1..256)) OPTIONAL,
	--Data File Name identifying the Data File. 		
	dataFileName  		UTF8String(SIZE(1..256)) OPTIONAL,	
	-- ECU Address
 	ecuAddress	 	PrintableString(SIZE(1..256)) OPTIONAL,	
	--Validation Key used to obtain Software Part Identifier from Target ECU. 
	validationKey 		PrintableString(SIZE(1..256)) OPTIONAL, 	
	--Part Identifier identifying the Software Part. 
	partIdentifier  	PrintableString(SIZE(1..256)) OPTIONAL,	
	--Data Block Sequence Number detailing where/when the exception or failure occurred
	dataBlockNumber 	INTEGER(1..65535) OPTIONAL,
	exceptionMessage	ExceptionMessage	
}

--Detailed Exception Message 
ExceptionMessage ::=SEQUENCE{	
	--Activity Name detailing where/when the exception or failure occurred
	activity  		PrintableString(SIZE(1..256)),
	--Action Name detailing where/when the exception or failure occurred
	action  		PrintableString(SIZE(1..256)),
	--detail the failure or exception. 
	exception   		PrintableString(SIZE(1..1024))
}

-- apply to  geea2.0 ota 2.15.3
ClientHmiVehicleSettings ::=SEQUENCE{
	--The over-the-air software download 
	--ON  the client is active i.e. the vehicle configuration will automatically synchronize with the backend in order to be able to discover and commission available assignments. 
	--OFF the client is inactive i.e. the vehicle configuration will no longer synchronize with the backend, assignments can no longer be discovered nor commissioned
	otaSetting		BOOLEAN  , 
	
	--Automatic synchronization of assignments 
	--ON - the client will perform automatic synchronization of assignments and notify the user of any available assignments
	--OFF - manual trigger from HMI is needed in order to discover available updates
	autoSync		BOOLEAN  ,

	--Automatic download of assignment data
	--ON - the client does not require manual user consent for downloading assignment data i.e. user consent for download is constant (GRANTED)
	--OFF - the client needs user consent before downloading assignment data
	autoDownload		BOOLEAN  ,

	--Automatic installation of assignments
	--ON - the client does not require manual user consent for installing assignments i.e. user consent for installation is constant (GRANTED)
	--OFF - the client needs user consent before installation
	autoInstallation	BOOLEAN  
}

-- The objective of this interface is to provide assignment data to vehicle.
-- apply to  geea2.0 ota 2.16.3
 AssignmentData ::=SEQUENCE{
	--Unique Identifier of the Installation Order, or software, associated to the notification
	installationOrderId	UTF8String(SIZE(1..256)),	
	timestamp		PrintableString(SIZE(1..32)),	
	--The download URL of the vbf file for software part. Need to support PKI and CDN Downloads
	urls			SEQUENCE OF PrintableString(SIZE(1..256))
 }
 
 -- The objective of this interface is to provide all VBF signatures for a specific installation order ID to vehicle
 -- provide all VBF signatures for a specific installation order ID to vehicle
 -- apply to  geea2.0 ota 2.18.3
 OtaAssignmentFileInfo ::=SEQUENCE{

	--Unique Identifier for the commissioned assignment
	installationOrderId     UTF8String(SIZE(1..256)),
	-- Contains all VBF signatures for a specific installation order ID
	assignFileInfos		SEQUENCE OF AssignmentFileInfo
}
 
AssignmentFileInfo ::=SEQUENCE{	
	--file name
	partidentifier		PrintableString(SIZE(1..256)),	
	--Signature hash for the file 
	softwarePartSignature	PrintableString(SIZE(1..256)),	
	--CRC32 ethernet polynominal
	fileCheckSum		PrintableString(SIZE(1..256))
}
	
-- FOTA END
 
AppId ::= ENUMERATED {
	ecarx		(0), -- using ecarx OTA Server
	geely		(1),  -- using geely It  OTA Server
	lynkCoEn	(2),	-- lynk&CO  international  OTA Server
	lynkCoCh	(3),	-- lynk&CO  chinese  OTA Server
	proton		(4), 	-- proton  OTA Server
	lotus		(5)	-- lotus  OTA Server
}

-- The objective of this interface is to provide the changed language setting of in-vehicle HMI to OTA server.
LanguageSetting ::= SEQUENCE {
	language	Language
}

Language ::= ENUMERATED {
	arabic (1),
	bulgarian (2),
	chineseTradCan (3),
	chineseSimpMan (4),
	chineseTradMan (5),
	czech (6),
	danish (7),
	dutch (8),
	australianEnglish (9),
	ukEnglish (10),
	americanEnglish (11),
	estonian (12),
	finnish (13),
	flemish (14),
	canadianFrench (15),
	french (16),
	german (17),
	greek (18),
	hungarian (19),
	italian (20),
	japanese (21),
	korean(22),-- (Han'Gul)
	latvian (23),
	lithuanian (24),
	norwegian (25),
	polish (26),
	brazilianPortuguese (27),
	portuguese (28),
	romanian (29),
	russian (30),
	slovak (31),
	slovene (32),
	spanish (33),
	americanSpanish (34),
	swedish (35),
	thai (36),
	turkish (37)	
}

END
