CA-ROU-031 {1 3 6 1 4 1 37916 3 8 3 0 3 1} DEFINITIONS AUTOMATIC TAGS ::= BEGIN

    IMPORTS 
        ResponseInfo    FROM FS-StandardTypes
        ;

    CA-ROU-031 ::= SEQUENCE {
        responseInfo    ResponseInfo,
        ...
    }
    
END
