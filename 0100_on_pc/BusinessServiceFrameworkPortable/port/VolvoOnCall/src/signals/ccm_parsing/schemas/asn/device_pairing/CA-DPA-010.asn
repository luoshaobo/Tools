CA-DPA-010 {1 3 6 1 4 1 37916 3 8 7 0 1 0} DEFINITIONS AUTOMATIC TAGS ::= BEGIN

    IMPORTS 
        DevicePairingId FROM CA-CommonTypes
        ;

    CA-DPA-010 ::= SEQUENCE {
        id               DevicePairingId,
        command          CHOICE {
           start   NULL,
           stop    NULL,
           ...
        },
        ...
    }
    
END
