CA-DEL-011 {1 3 6 1 4 1 37916 3 8 5 0 1 1} DEFINITIONS AUTOMATIC TAGS ::= BEGIN
--CA-TIM-041 {1 3 6 1 4 1 37916 3 8 6 0 4 1} DEFINITIONS AUTOMATIC TAGS ::= BEGIN

    IMPORTS 
        ResponseInfo    FROM FS-StandardTypes
        CertRepMessage  FROM GeneralModule
		;

    CA-DEL-011 ::= SEQUENCE {
        responseInfo    ResponseInfo,
        cp               CertRepMessage OPTIONAL,
        ...
    }
    
END
