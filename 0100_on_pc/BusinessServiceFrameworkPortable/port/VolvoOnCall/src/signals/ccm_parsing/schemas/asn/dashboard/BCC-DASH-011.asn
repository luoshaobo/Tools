BCC-DASH-011 {1 3 6 1 4 1 37916 3 6 5 0 1 1} DEFINITIONS AUTOMATIC TAGS ::= BEGIN

    IMPORTS 
        Envelope, ResponseInfo    FROM FS-StandardTypes
    ;

    BCC-DASH-011 ::= SEQUENCE {
        responseInfo    ResponseInfo,
        time    GeneralizedTime OPTIONAL, 
        status  Envelope OPTIONAL,
        ...
    }
END
