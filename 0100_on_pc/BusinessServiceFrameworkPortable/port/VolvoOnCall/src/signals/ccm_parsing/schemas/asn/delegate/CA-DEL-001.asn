CA-DEL-001 {1 3 6 1 4 1 37916 3 8 5 0 0 1} DEFINITIONS AUTOMATIC TAGS ::= BEGIN
--CA-TIM-030 {1 3 6 1 4 1 37916 3 8 6 0 3 0} DEFINITIONS AUTOMATIC TAGS ::= BEGIN


    CA-DEL-001 ::= SEQUENCE {
        ...
    }
    
END
