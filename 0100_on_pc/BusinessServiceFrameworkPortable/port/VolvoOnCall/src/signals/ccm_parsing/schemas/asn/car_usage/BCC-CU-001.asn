BCC-CU-001 {1 3 6 1 4 1 37916 3 6 4 0 0 1} DEFINITIONS AUTOMATIC TAGS ::= BEGIN

    IMPORTS 
        Envelope                           FROM FS-StandardTypes
		TripStatus                         FROM BCC-CommonTypes
        ;
	
    BCC-CU-001 ::= SEQUENCE {
        time    GeneralizedTime OPTIONAL, 
		tripStatus TripStatus OPTIONAL,
        status  Envelope OPTIONAL,
        ...
    }
	
END
