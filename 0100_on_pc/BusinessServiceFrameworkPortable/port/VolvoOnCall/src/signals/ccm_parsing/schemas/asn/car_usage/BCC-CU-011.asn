BCC-CU-011 {1 3 6 1 4 1 37916 3 6 4 0 1 1} DEFINITIONS AUTOMATIC TAGS ::= BEGIN

    IMPORTS 
        Envelope, ResponseInfo    FROM FS-StandardTypes
   		TripStatus                FROM BCC-CommonTypes
    ;

    BCC-CU-011 ::= SEQUENCE {
        responseInfo    ResponseInfo,
        time       GeneralizedTime OPTIONAL, 
		tripStatus TripStatus OPTIONAL,
        status     Envelope OPTIONAL,
        ...
    }
END
