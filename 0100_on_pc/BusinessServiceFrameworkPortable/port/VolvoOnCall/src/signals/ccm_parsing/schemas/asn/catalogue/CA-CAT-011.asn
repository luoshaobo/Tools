--CA-CAT-002 {1 3 6 1 4 1 37916 3 8 4 0 0 2} DEFINITIONS AUTOMATIC TAGS ::= BEGIN
CA-CAT-011 {1 3 6 1 4 1 37916 3 8 4 0 1 1} DEFINITIONS AUTOMATIC TAGS ::= BEGIN
--CA-DEL-002 {1 3 6 1 4 1 37916 3 8 5 0 0 2} DEFINITIONS AUTOMATIC TAGS ::= BEGIN
--CA-TIM-002 {1 3 6 1 4 1 37916 3 8 6 0 0 2} DEFINITIONS AUTOMATIC TAGS ::= BEGIN
--CA-TIM-011 {1 3 6 1 4 1 37916 3 8 6 0 1 1} DEFINITIONS AUTOMATIC TAGS ::= BEGIN
--CA-TIM-021 {1 3 6 1 4 1 37916 3 8 6 0 2 1} DEFINITIONS AUTOMATIC TAGS ::= BEGIN
--CA-TIM-031 {1 3 6 1 4 1 37916 3 8 6 0 3 1} DEFINITIONS AUTOMATIC TAGS ::= BEGIN


    IMPORTS 
        ResponseInfo    FROM FS-StandardTypes
        ;

    CA-CAT-011 ::= SEQUENCE {
        responseInfo    ResponseInfo,
        ...
    }
    
END
