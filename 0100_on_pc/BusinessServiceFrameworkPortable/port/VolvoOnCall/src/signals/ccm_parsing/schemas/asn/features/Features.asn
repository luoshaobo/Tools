Features {1 3 6 1 4 1 37916 3 0 2} DEFINITIONS AUTOMATIC TAGS ::= BEGIN

    IMPORTS 
        Uri, UUID                  FROM FS-CommonTypes
        ;

    Features ::= SEQUENCE {
        thiz                    Uri    OPTIONAL,
        feature                 SEQUENCE OF Feature OPTIONAL,
        ...
    }
    
    Feature ::= SEQUENCE {
        name                UTF8String,
        enabled             BOOLEAN,
        visible             BOOLEAN,
        uri                 Uri,
        --address             Address      OPTIONAL,
        icon                Uri          OPTIONAL,
        description         UTF8String   OPTIONAL,
        tags                SEQUENCE (SIZE(1..maxNumberOfTags)) OF Tag OPTIONAL,
        --communicationInfo   CommunicationInfo OPTIONAL,
        --extendedInfo        Envelope OPTIONAL,
        ...
    }

    --Address ::= CHOICE {
    --   uri         Uri,
    --   featureId   OBJECT IDENTIFIER,
    --   instanceId  UUID,
    --   ... 
    --}


    --CommunicationInfo ::= SEQUENCE {
    --   protocols           SEQUENCE (SIZE(1..maxNumberOfProtocols)) OF Protocol,
    --   signalFlowVersions  SEQUENCE (SIZE(1..maxNumberOfSignalFlowVersions)) OF INTEGER OPTIONAL,
    --   schemaVersion       INTEGER,
    --   preliminaryVersion  INTEGER OPTIONAL,
    --   ... 
    --}

    --Protocol ::= ENUMERATED {
    --   http-xml  (0),
    --   http-ccm  (1),
    --   mqtt-ccm  (2),
    --   ... 
    --}

    maxNumberOfFeatures            INTEGER ::= 500
    maxNumberOfTags                INTEGER ::= 5000
    maxNumberOfProtocols           INTEGER ::= 100
    maxNumberOfSignalFlowVersions  INTEGER ::= 100

    Tag ::= UTF8String

END
