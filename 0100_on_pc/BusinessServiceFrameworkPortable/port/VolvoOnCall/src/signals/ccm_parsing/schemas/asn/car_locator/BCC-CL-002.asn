BCC-CL-002 {1 3 6 1 4 1 37916 3 6 3 0 0 2} DEFINITIONS AUTOMATIC TAGS ::= BEGIN

    IMPORTS 
        ResponseInfo    FROM FS-StandardTypes;

    BCC-CL-002 ::= SEQUENCE {
        responseInfo           ResponseInfo,
        ...
    }
    
END
