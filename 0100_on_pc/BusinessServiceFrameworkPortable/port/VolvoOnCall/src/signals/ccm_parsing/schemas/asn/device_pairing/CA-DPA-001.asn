CA-DPA-001 {1 3 6 1 4 1 37916 3 8 7 0 0 1} DEFINITIONS AUTOMATIC TAGS ::= BEGIN

    IMPORTS 
        DevicePairingId, VehicleInfo FROM CA-CommonTypes
        ;

    CA-DPA-001 ::= SEQUENCE {
        id               DevicePairingId,
        command          CHOICE {
           start   NULL,
           stop    NULL,
           ...
        },
        remoteConnectionTimeout   GeneralizedTime  OPTIONAL, -- Use TIME if ASN.1 2008
        pairingTimeout            GeneralizedTime  OPTIONAL, -- Use TIME if ASN.1 2008
        vehicleInfo               VehicleInfo  OPTIONAL,
        ...
    }
    
END
