CCM-SMS-Payload {1 3 6 1 4 1 37916 6 2 2} DEFINITIONS AUTOMATIC TAGS ::= BEGIN

    -- =================================================================
    --
    -- Payload for Connectivity Compact Message SMS backup message
    --
    -- =================================================================

    IMPORTS
           UINT4  FROM CCM-CommonTypes
    ;

    CCM-SMS-Payload ::= SEQUENCE {
        contentType            ContentType,   -- Part of OID
        content                OCTET STRING (SIZE(31))
    }

    ContentType ::= RELATIVE-OID
    --ContentType ::= SEQUENCE (SIZE(1..6)) OF UINT4

END
