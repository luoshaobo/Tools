FS-StandardTypes {1 3 6 1 4 1 37916 3 0 1 0 0 1} DEFINITIONS AUTOMATIC TAGS ::= BEGIN
    -- 1 - Basic types
    UINT8  ::= INTEGER (0..255)
    UINT16 ::= INTEGER (0..65535)
    UINT32 ::= INTEGER (0..4294967295)

    FSVIN   ::= OCTET STRING (SIZE(17))
    FSSubjectKeyIdentifier   ::= OCTET STRING (SIZE(20))  -- RFC 5280, section 4.2.1.2


    -- 2 - Envelope types
    ContentType ::= CHOICE {
        oid        OBJECT IDENTIFIER,
        vccOid     RELATIVE-OID,  -- Relative OID prepend {1 3 6 1 4 1 37916}
        vccBasicCarStatusOid  RELATIVE-OID,  -- Relative OID prepend {1 3 6 1 4 1 37916 3 7}
        ...
    }

    Encoding ::= ENUMERATED {
       ber      (0),
       cer      (1),
       der      (2),
       oer      (3),
       per      (4),
       uper     (5), -- Implicit if contentEncoding not included
       xer      (6),
       xml      (7),
       ...
    }
    Envelope ::= SEQUENCE {
        contentType        ContentType,   -- OID
        contentEncoding    Encoding OPTIONAL,
        contentVersion     VersionInfo OPTIONAL,
        content            OCTET STRING,
        ...
    }

    -- 3 - Version information types
    VersionInfo ::= SEQUENCE {
        signalFlowVersion   INTEGER OPTIONAL,
        schemaVersion       INTEGER,
        preliminaryVersion  INTEGER OPTIONAL,
        ...
    }

    -- 4 - Channel configuration types
    ChannelConfiguration ::= CHOICE {
        wifi WiFiChannelConfig,
        sms  SmsChannelConfig,
        ble  BleChannelConfig,
        data DataChannelConfig,
        ...
     }

    SmsChannelConfig ::= SEQUENCE {
        allowed		BOOLEAN,
        smsmessages	SEQUENCE OF ContentType OPTIONAL,
        ...
    }
    BleChannelConfig ::= SEQUENCE {
        allowed		BOOLEAN,
        blemessages	SEQUENCE OF ContentType OPTIONAL,
        ...
    }
    WiFiChannelConfig ::= SEQUENCE {
        allowed		BOOLEAN,
		wifiType    WiFiType,
        wifimessages	SEQUENCE OF ContentType OPTIONAL,
        ...
    }
    DataChannelConfig ::= SEQUENCE {
        allowed			BOOLEAN,
		subscription	DataSubscription,
        datamessages		SEQUENCE OF ContentType OPTIONAL,
        ...
    }
	
	DataSubscription ::= ENUMERATED {
     any,
     vccHighVolume,
     vccLowVolume,
     user,
	...
	}
	
	WiFiType ::= ENUMERATED {
		 any,
		 workshop,
		 vehicleHotspot,
		 ...
	}

    -- 5 - Response information types
    ResponseInfo ::= CHOICE {
        success     SuccessInfo,
        error       ErrorInfo,
        acknowledge AcknowledgeInfo,
        ...
    }
    AcknowledgeInfo ::= SEQUENCE {
        messageId   UINT16,
        info        UTF8String  OPTIONAL,
        ...
    }
    SuccessInfo ::= SEQUENCE {
        messageId   UINT16 OPTIONAL,
        code        SuccessCode OPTIONAL,
        info        UTF8String  OPTIONAL,
        ...
    }

    ErrorInfo ::= SEQUENCE {
        messageId   UINT16 OPTIONAL,
        code        ErrorCode,
        info        UTF8String  OPTIONAL,
        size1Info   INTEGER     OPTIONAL,
        ...
    }
    SuccessCode ::= ENUMERATED {
		ok						   (200),
        created                    (201),  -- See CoAP 2.01
        deleted                    (202),  -- See CoAP 2.02
        valid                      (203),  -- See CoAP 2.03
        changed                    (204),  -- See CoAP 2.04
        content                    (205),  -- See CoAP 2.05
        ...
      }
    ErrorCode ::= ENUMERATED {
        badRequest                 (400),  -- See CoAP 4.00
        unauthorized               (401),  -- See CoAP 4.01
        badOption                  (402),  -- See CoAP 4.02
        forbidden                  (403),  -- See CoAP 4.03
        notFound                   (404),  -- See CoAP 4.04
        methodNotAllowed           (405),  -- See CoAP 4.05
        notAcceptable              (406),  -- See CoAP 4.06
        preconditionFailed         (412),  -- See CoAP 4.12
        requestEntityTooLarge      (413),  -- See CoAP 4.13
        unsupportedContentFormat   (415),  -- See CoAP 4.15
        internalError              (501),  -- See CoAP 5.01
        badGateway                 (502),  -- See CoAP 5.02
        serviceUnavailable         (503),  -- See CoAP 5.03
        gatewayTimeout             (504),  -- See CoAP 5.04
        proxyingNotSupported       (505),  -- See CoAP 5.05
        ...
     }

END
