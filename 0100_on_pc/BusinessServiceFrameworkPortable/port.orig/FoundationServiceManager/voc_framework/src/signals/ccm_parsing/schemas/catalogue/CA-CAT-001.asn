CA-CAT-001 {1 3 6 1 4 1 37916 3 8 4 0 0 1} DEFINITIONS AUTOMATIC TAGS ::= BEGIN

    IMPORTS 
        Certificate     FROM PKIX1Explicit88 { iso(1) identified-organization(3) dod(6)
                                               internet(1) security(5) mechanisms(5)
                                               pkix(7) id-mod(0) id-pkix1-explicit(18)}  -- => RFC 5280

       ;
        

    CA-CAT-001 ::= SEQUENCE {
        certificates     SEQUENCE SIZE (1..maxNoOfCertificates) OF Certificate,
        ...
    }

    maxNoOfCertificates INTEGER ::= 20
    
END
