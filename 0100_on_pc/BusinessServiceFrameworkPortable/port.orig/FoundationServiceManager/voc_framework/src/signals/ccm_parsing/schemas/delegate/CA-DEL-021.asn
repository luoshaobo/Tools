CA-DEL-021 {1 3 6 1 4 1 37916 3 8 5 0 2 1} DEFINITIONS AUTOMATIC TAGS ::= BEGIN

    IMPORTS 
        ResponseInfo    FROM FS-StandardTypes
        RevRepContent   FROM GeneralModule
		;


    CA-DEL-021 ::= SEQUENCE {
        responseInfo     ResponseInfo,
        rp               RevRepContent OPTIONAL,
        ...
    }

    
END
