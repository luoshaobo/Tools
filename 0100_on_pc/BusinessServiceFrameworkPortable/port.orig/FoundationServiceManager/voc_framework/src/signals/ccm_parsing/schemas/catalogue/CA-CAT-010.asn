CA-CAT-010 {1 3 6 1 4 1 37916 3 8 4 0 1 0} DEFINITIONS AUTOMATIC TAGS ::= BEGIN

    IMPORTS 
        SubjectKeyIdentifier   FROM PKIX1Implicit88 {iso(1) identified-organization(3)
                         dod(6) internet(1) security(5) mechanisms(5) pkix(7)
                         id-mod(0) id-pkix1-implicit(19) }  -- => RFC 5280
        ;


    CA-CAT-010 ::= SEQUENCE {
        subjectKeyIdentifiers  SEQUENCE SIZE (1..maxNoOfIdentifiers) OF SubjectKeyIdentifier,
        ...
    }
    
    maxNoOfIdentifiers INTEGER ::= 50

END
