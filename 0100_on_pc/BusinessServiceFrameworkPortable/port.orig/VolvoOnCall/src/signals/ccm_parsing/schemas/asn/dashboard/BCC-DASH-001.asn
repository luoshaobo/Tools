BCC-DASH-001 {1 3 6 1 4 1 37916 3 6 5 0 0 1} DEFINITIONS AUTOMATIC TAGS ::= BEGIN

    IMPORTS 
        Envelope                           FROM FS-StandardTypes
        ;
	
    BCC-DASH-001 ::= SEQUENCE {
        time    GeneralizedTime OPTIONAL, 
        status  Envelope OPTIONAL,
        ...
    }
	
END
