CA-DPA-020 {1 3 6 1 4 1 37916 3 8 7 0 2 0} DEFINITIONS AUTOMATIC TAGS ::= BEGIN

    IMPORTS 
        DevicePairingId FROM CA-CommonTypes
        ;

    CA-DPA-020 ::= SEQUENCE {
        id               DevicePairingId,
        data             BIT STRING,
        ...
    }
    
END
