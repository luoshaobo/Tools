CA-DPA-021 {1 3 6 1 4 1 37916 3 8 7 0 2 1} DEFINITIONS AUTOMATIC TAGS ::= BEGIN

    IMPORTS 
        ResponseInfo    FROM FS-StandardTypes
        DevicePairingId FROM CA-CommonTypes
        ;

    CA-DPA-021 ::= SEQUENCE {
        id              DevicePairingId,
        responseInfo    ResponseInfo,
        data            BIT STRING OPTIONAL,
        ...
    }
    
END
