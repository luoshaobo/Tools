BCC-CL-011 {1 3 6 1 4 1 37916 3 6 3 0 1 1} DEFINITIONS AUTOMATIC TAGS ::= BEGIN

    IMPORTS 
       Location, MinimumSetOfLocationData FROM BCC-LocationTypes
        ResponseInfo    FROM FS-StandardTypes
       ;

    BCC-CL-011 ::= SEQUENCE {
        responseInfo    ResponseInfo,
        location       CHOICE {
           extendedLocation   Location,
           minimumLocation    MinimumSetOfLocationData,
           ...
        } OPTIONAL,
        ...
    }
END
