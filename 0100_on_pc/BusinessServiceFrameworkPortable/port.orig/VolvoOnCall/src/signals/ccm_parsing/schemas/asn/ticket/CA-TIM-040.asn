--CA-DEL-010 {1 3 6 1 4 1 37916 3 8 5 0 1 0} DEFINITIONS AUTOMATIC TAGS ::= BEGIN
CA-TIM-040 {1 3 6 1 4 1 37916 3 8 6 0 4 0} DEFINITIONS AUTOMATIC TAGS ::= BEGIN

    IMPORTS 
        CertReqMessages FROM GeneralModule  -- => X.843
		--CertReqMessages FROM GeneralModule {iso(1) identified-organization(3)
         --                    dod(6) internet(1) security(5) mechanisms(5) pkix(7)
          --                   id-mod(0) id-mod-crmf2005(36)}  => RFC 4211, section 3

       ;

    CA-TIM-040 ::= SEQUENCE {
        cr               CertReqMessages,
        ...
    }
    
END
