CarSettings {1 3 6 1 4 1 37916 3 0 5} DEFINITIONS AUTOMATIC TAGS ::= BEGIN

    IMPORTS 
        Uri, UUID        FROM FS-CommonTypes
        ;

    CarSettings ::= SEQUENCE {
        thiz                    Uri OPTIONAL,
        packages                SEQUENCE (SIZE(1..maxNumberOfPackages)) OF Package,
        ...
    }
    
    Package ::= SEQUENCE {
        name                UTF8String,
        settings            SEQUENCE (SIZE(1..maxNumberOfSettings)) OF Setting OPTIONAL,
        ...
    }

    Setting ::= SEQUENCE {
        name                UTF8String,
        value               UTF8String,
        lastModified        TIME OPTIONAL,
        ...
    }

    maxNumberOfPackages            INTEGER ::= 5000
    maxNumberOfSettings            INTEGER ::= 5000

END
