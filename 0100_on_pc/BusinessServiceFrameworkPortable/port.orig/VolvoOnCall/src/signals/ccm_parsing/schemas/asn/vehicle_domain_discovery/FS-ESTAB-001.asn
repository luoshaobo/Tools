FS-ESTAB-001 {1 3 6 1 4 1 37916 3 0 6 0 0 1} DEFINITIONS AUTOMATIC TAGS ::= BEGIN

    FS-ESTAB-001 ::= SEQUENCE {
        rescources  SEQUENCE (SIZE(1..maxSRescources)) OF Rescource  OPTIONAL,
        ...
    }

    Rescource ::= SEQUENCE {
       name                UTF8String,
       rescourceVersion    UTF8String OPTIONAL,
       ...
     }

    maxSRescources INTEGER ::= 100
    
END
