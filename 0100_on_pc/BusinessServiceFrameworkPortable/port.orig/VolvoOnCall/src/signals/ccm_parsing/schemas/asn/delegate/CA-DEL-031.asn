CA-DEL-031 {1 3 6 1 4 1 37916 3 8 5 0 3 1} DEFINITIONS AUTOMATIC TAGS ::= BEGIN

    IMPORTS 
        ResponseInfo    FROM FS-StandardTypes
        CertRepMessage  FROM GeneralModule
		;

    CA-DEL-031 ::= SEQUENCE {
        responseInfo     ResponseInfo,
        kup              CertRepMessage OPTIONAL,
        ...
    }
    
END
