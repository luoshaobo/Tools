CA-CommonTypes {1 3 6 1 4 1 37916 3 8 1 0 0 2} DEFINITIONS AUTOMATIC TAGS ::= BEGIN

    IMPORTS 
        FSVIN    FROM FS-StandardTypes
        ;

    DevicePairingId ::= CHOICE {
      vin FSVIN,
      uuid UUID,
      ...
    }

    CASubjectKeyIdentifier   ::= OCTET STRING (SIZE(20))  -- RFC 5280, section 4.2.1.2

    SessionId      ::= OCTET STRING (SIZE(16)) -- As defined in CCM

    Uri ::= UTF8String

    UUID ::= OCTET STRING (SIZE(16))

    VehicleInfo ::= SEQUENCE {   
        vin       INTEGER, --TBD
        model     INTEGER, --TBD
        modelyear INTEGER,
        ...
    }

    --X509Certificate      ::= BIT STRING  - - Certificate ASN.1 type according to RFC5280
    
END
