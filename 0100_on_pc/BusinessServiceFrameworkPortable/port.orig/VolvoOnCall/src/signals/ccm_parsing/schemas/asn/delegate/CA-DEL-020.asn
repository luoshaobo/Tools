CA-DEL-020 {1 3 6 1 4 1 37916 3 8 5 0 2 0} DEFINITIONS AUTOMATIC TAGS ::= BEGIN

    IMPORTS 
        RevReqContent   FROM GeneralModule
		;

    CA-DEL-020 ::= SEQUENCE {
        rr               RevReqContent,
        ...
    }

END
