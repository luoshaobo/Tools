BCC-PC-002 {1 3 6 1 4 1 37916 3 6 9 0 0 2} DEFINITIONS AUTOMATIC TAGS ::= BEGIN

    IMPORTS 
        ResponseInfo    FROM FS-StandardTypes
        ServiceStatus, ServiceWarning, TimerInfo    FROM BCC-PC-010
        ;

    BCC-PC-002 ::= SEQUENCE { -- what about seat selection, garage safe, temp sensor ?
        responseInfo    ResponseInfo,
        timerStatus     TimerInfo OPTIONAL,
--      calenderStatus  CalenderStatus OPTIONAL, !Needs more elaboration!
        status          ServiceStatus,
        warning         ServiceWarning OPTIONAL,
        ...
    }
    
END
