BCC-CL-020 {1 3 6 1 4 1 37916 3 6 3 0 2 0} DEFINITIONS AUTOMATIC TAGS ::= BEGIN

    IMPORTS 
       Location, MinimumSetOfLocationData FROM BCC-LocationTypes;

    BCC-CL-020 ::= SEQUENCE {
        location       CHOICE {
           extendedLocation   Location,
           minimumLocation    MinimumSetOfLocationData,
           ...
        },
        ...
    }

END
