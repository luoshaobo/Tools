ExpiryNotification {1 3 6 1 4 1 37916 3 0 3} DEFINITIONS AUTOMATIC TAGS ::= BEGIN

    ExpiryNotification ::= SEQUENCE {
        resources    SEQUENCE (SIZE(1..10)) OF Resource,
        ...
    }

    Resource  ::= SEQUENCE {
        name       UTF8String,
        parameters UTF8String OPTIONAL,
        evictionType EvictionType,
        ...
    }

    EvictionType ::= ENUMERATED {
        reconnect,
        invalidate	,
        ...
    }

END
