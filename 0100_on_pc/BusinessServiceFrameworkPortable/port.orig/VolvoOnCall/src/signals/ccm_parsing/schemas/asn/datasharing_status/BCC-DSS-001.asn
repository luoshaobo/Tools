BCC-DSS-001 {1 3 6 1 4 1 37916 3 6 6 0 0 1} DEFINITIONS AUTOMATIC TAGS ::= BEGIN

    IMPORTS 
        Envelope                           FROM FS-StandardTypes
		DatasharingSetting                 FROM BCC-CommonTypes
        ;
	
    BCC-DSS-001 ::= SEQUENCE {
        time                  GeneralizedTime  OPTIONAL, 
		datasharingSetting    DatasharingSetting OPTIONAL,
        ...
    }
	
END
