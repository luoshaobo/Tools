BCC-CL-001 {1 3 6 1 4 1 37916 3 6 3 0 0 1} DEFINITIONS AUTOMATIC TAGS ::= BEGIN

    BCC-CL-001 ::= SEQUENCE {
        operation  CHOICE {
             locationAdvert BCCCL001LocationAdvertParameters,
             ...
        },
        options SEQUENCE {
             ...
        } OPTIONAL,
        ...
    }

    BCCCL001LocationAdvertParameters ::= SEQUENCE {
        advert   Adverts,
        ...
    }

    Adverts::= ENUMERATED {
        honk          (0),
        flash         (1),
        honkAndFlash  (2),
        ...
    }

END
