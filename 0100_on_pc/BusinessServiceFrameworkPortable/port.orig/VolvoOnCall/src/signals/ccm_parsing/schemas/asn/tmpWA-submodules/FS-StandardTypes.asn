FS-StandardTypes {1 3 6 1 4 1 37916 3 0 1 0 0 1} DEFINITIONS AUTOMATIC TAGS ::= BEGIN
    -- 1 - Basic types
    UINT8  ::= INTEGER (0..255)
    UINT16 ::= INTEGER (0..65535)
    UINT32 ::= INTEGER (0..4294967295)

    VIN   ::= OCTET STRING (SIZE(17))


    -- 2 - Envelope types
    ContentType ::= OBJECT IDENTIFIER
    Encoding ::= ENUMERATED {
       ber      (0),
       cer      (1),
       der      (2),
       oer      (3),
       per      (4),
       uper     (5),
       xer      (6),
       xml      (7),
       ...
    }
    Envelope ::= SEQUENCE {
        contentType        ContentType,   -- OID
        contentEncoding    Encoding,
        contentVersion     VersionInfo OPTIONAL,
        content            OCTET STRING,
        ...
    }

    -- 3 - Version information types
    VersionInfo ::= SEQUENCE {
        signalFlowVersion   INTEGER OPTIONAL,
        schemaVersion       INTEGER,
        preliminaryVersion  INTEGER OPTIONAL,
        ...
    }

    -- 4 - Response information types
    ResponseInfo ::= CHOICE {
        success SuccessInfo,
        error   ErrorInfo,
        ...
    }
    SuccessInfo ::= SEQUENCE {
        code        SuccessCode OPTIONAL,
        info        UTF8String  OPTIONAL,
        ...
    }
    ErrorInfo ::= SEQUENCE {
        code        ErrorCode,
        info        UTF8String  OPTIONAL,
        size1Info   INTEGER     OPTIONAL,
        ...
    }
    SuccessCode ::= ENUMERATED {
        created                    (201),  -- See CoAP 2.01
        deleted                    (202),  -- See CoAP 2.02
        valid                      (203),  -- See CoAP 2.03
        changed                    (204),  -- See CoAP 2.04
        content                    (205),  -- See CoAP 2.05
        ...
      }
    ErrorCode ::= ENUMERATED {
        badRequest                 (400),  -- See CoAP 4.00
        unauthorized               (401),  -- See CoAP 4.01
        badOption                  (402),  -- See CoAP 4.02
        forbidden                  (403),  -- See CoAP 4.03
        notFound                   (404),  -- See CoAP 4.04
        methodNotAllowed           (405),  -- See CoAP 4.05
        notAcceptable              (406),  -- See CoAP 4.06
        preconditionFailed         (412),  -- See CoAP 4.12
        requestEntityTooLarge      (413),  -- See CoAP 4.13
        unsupportedContentFormat   (415),  -- See CoAP 4.15
        internalError              (501),  -- See CoAP 5.01
        badGateway                 (502),  -- See CoAP 5.02
        serviceUnavailable         (503),  -- See CoAP 5.03
        gatewayTimeout             (504),  -- See CoAP 5.04
        proxyingNotSupported       (505),  -- See CoAP 5.05
        ...
     }
END
